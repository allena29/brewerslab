module tester {
	namespace "http://confvillain.mellon-collie.net/tester/";
	prefix tester;

	list list1 {
		key key1;

		leaf key1 {
			type string;
		}

    leaf nonkey {
      type string;
    }
	}
}
